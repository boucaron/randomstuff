import CommonCameraSketch

try:
   CommonCameraSketch.SetOrGetCameraSketch(sketch = ActiveSketch, getAction = False)    
except NameError:
   FreeCAD.Console.PrintMessage("Macros must be called inside a sketch\n")
